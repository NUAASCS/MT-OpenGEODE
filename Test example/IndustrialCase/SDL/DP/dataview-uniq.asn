TASTE-Dataview DEFINITIONS ::=
BEGIN
-- MP1
--p1:Device_Current_State_Info
Device-Current-StateInfo ::= SEQUENCE { content Message}
--p2:Device_PowerOn_Command
Device-PowerOn-Command ::= SEQUENCE { content Message}
--p3:Device_Self-Check_Result
Device-SelfCheck-Result ::= SEQUENCE { content Message}
--p4:Launch Control Computer Self-Check Results
Control-Computer-SelfCheck-Result ::= SEQUENCE { content Message}
--p5:Device_PowerOn_Result
Device-PowerOn-Result ::= Message
--p6:Device_PowerOn1_Result
Device-PowerOn1-Result ::= Message
--p7:Device_PowerOn2_Result
Device-PowerOn2-Result ::= Message
--p8:Device_PowerOn3_Result
Device-PowerOn3-Result ::= Message

--Trigger
Trigger::= SEQUENCE { content Message}
Trigger-1::= SEQUENCE { content Message}
Trigger-2::= SEQUENCE { content Message}

--Error
Error::=SEQUENCE { content Message}

--Concrete Errors
errorCCSR Message::={0} 
errorDSR Message::={0} 
errorDP1 Message::={0}
errorDP2 Message::={0}
errorDP3 Message::={0}

Bit   ::= INTEGER (0..1)
Message ::= SEQUENCE (SIZE(0..127)) OF Bit


--other
MyChoice ::= CHOICE {
    a CHOICE {
        b CHOICE {
            c BOOLEAN,
            d BOOLEAN
        },
        e BOOLEAN
    },
    f BOOLEAN
}

Some-Thing ::= MyInteger

MyInteger   ::= INTEGER (0..255)

My-OctStr    ::= OCTET STRING (SIZE (0..20))

SeqOf ::= SEQUENCE (SIZE(0..100)) OF MyInteger



Type1 ::= INTEGER(0..1)
Type2 ::= BOOLEAN

Toto ::= SEQUENCE { elem-1 Type1, elem-2 Type2 }

SeqBool ::= SEQUENCE(SIZE(1..5)) OF BOOLEAN

default-seqof SeqOf ::= {4,7,9}
default-str My-OctStr ::= 'DEADBEEF'H


END
